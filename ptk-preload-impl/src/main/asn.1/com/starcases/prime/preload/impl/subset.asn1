Impl DEFINITIONS AUTOMATIC TAGS ::= BEGIN

	--------------------------------------------------------------------
	-- PrimeSubset List
	--------------------------------------------------------------------
  	PrimeSubsetListAsn ::= SEQUENCE OF PrimeSubsetAsn

	--------------------------------------------------------------------
	-- PrimeSubset
	--------------------------------------------------------------------
	PrimeSubsetAsn ::= SEQUENCE
	{
	   primes                   PrimeListItemsAsn,
	   maxOffsetAssigned		INTEGER
	}

	--------------------------------------------------------------------
	-- PrimeBase - Prime + associated list of base items or list of lists
	-- of base items.
	--------------------------------------------------------------------
	PrimeBasesAsn ::= SEQUENCE
	{
	   prime					INTEGER,
	   bases                    CHOICE { PrimeBaseListAsn, PrimeListItemsAsn }
	}

	--------------------------------------------------------------------
	-- List of Lists of P
	--------------------------------------------------------------------
	PrimeBaseListAsn ::= SEQUENCE OF PrimeListItemsAsn

	--------------------------------------------------------------------
	-- List of base items
	--------------------------------------------------------------------
	PrimeListItemsAsn ::= SEQUENCE
	{
	 	primelist  SEQUENCE OF INTEGER
	}

END
